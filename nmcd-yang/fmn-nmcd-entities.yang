module fmn-nmcd-entities {
  yang-version 1.1;

  namespace "urn:fmn:params:xml:ns:yang:nmcd-entities";

  prefix nmcd-entities;

  import fmn-nmcd-types {
    prefix nmcd;
  }

  import fmn-nmcd-interfaces {
    prefix interface;
  }

  import ietf-inet-types {
    prefix inet;
  }

  organization
    "Federated Mission Networking (FMN) XX Working Group";

  contact
    "Editor:   some-one
               <mailto:your-email@example.com>";

  description
    "This module defines the NMCD-wide entity information.";

  revision 2019-12-31 {
    description
      "Initial version";
    reference
      "FMN Spiral 4 Service Instructions for Protected Core Networking";
  }

  grouping e-node-grouping {
    description "Enforcement Node information";

    leaf id {
      type nmcd:enode-id;
      description "The Enforcement Node identifier";
    }

    uses nmcd:descriptor-grouping;

    leaf-list advertised-prefix {
      type inet:ip-prefix;

      description "The list of IP prefixes advertised by this E-Node";
    }

    container certificate {
      description "Credentials information of the Enforcement Node";

      uses nmcd:certificate-grouping;
    }

    list pcn-1 {
      key "local-id";
      max-elements 65536;

      description "The list of PCN-1 interfaces in the Enforcement Node";

      uses interface:pcn-1-grouping;
    }

    list pcn-2 {
      key "local-id";
      max-elements 65536;

      description
        "The list of PCN-2 interfaces in the Enforcement Node";

      uses interface:pcn-2-enode-grouping;
    }
  }

  grouping p-func-grouping {
    description "Protection Functionality information";

    leaf id {
      type nmcd:pfunc-id;
      mandatory true;
      description "The Protection Functionality identifier";
    }

    uses nmcd:descriptor-grouping;

    leaf-list advertised-prefix {
      type inet:ip-prefix;

      description
        "The list of IP prefixes attached to this Protection Functionality";
    }

    container certificate {
      presence true;
      description
        "Credentials information of the Protection Functionality";

      uses nmcd:certificate-grouping;
    }

    list pcn-2 {
      key "local-id";
      min-elements 1;
      max-elements 65536;

      description
        "The list of PCN-2 interfaces in the Protection Functionality";

      uses interface:pcn-2-pfunctionality-grouping;
    }
  }
}
