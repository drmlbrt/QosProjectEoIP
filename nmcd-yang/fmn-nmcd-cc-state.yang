module fmn-nmcd-cc-state {
  yang-version 1.1;

  namespace "urn:fmn:params:xml:ns:yang:nmcd-cc-state";

  prefix nmcd-cc-state;

  import fmn-nmcd-types {
    prefix nmcd;
  }

  import fmn-nmcd-sla {
    prefix sla;
  }

  import fmn-nmcd-interfaces {
    prefix iface;
  }

  import ietf-inet-types {
    prefix inet;
  }

  organization
    "Federated Mission Networking (FMN) XX Working Group";

  contact
    "Editor:   some-one
               <mailto:your-email@example.com>";

  description
    "This module defines the NMCD-wide Protected Core Segment (PCS)
    abstraction.  The abstraction is exchanged in the NMCD federation by
    entities to form the PCS Operational Picture (PCSOP).";

  revision 2019-12-31 {
    description
      "Initial version";
    reference
      "FMN Spiral 4 Service Instructions for Protected Core Networking";
  }

  grouping cc-state-grouping {
    description "The abstraction of a Coloured Cloud.";

    leaf id {
      type nmcd:cc-id;
      mandatory true;
      description "The identifier of the CC.";
    }

    leaf originator-id {
      type nmcd:pcs-id;
      description
        "The originating PCS of this CC information. May be omitted if the
        information is originated by the CC itself.";
    }

    leaf-list reachable-prefix {
      type inet:ip-prefix;
      description
        "The list of currently reachable IP-prefixes through this
        P-functionality.";
    }

    list pcn-2 {
      key "id";
      min-elements 1;
      max-elements 65536;
      uses iface:pcn2-state-grouping;
      description
        "List of properties PCN-2 interfaces.";
    }

    list sla {
      key "id";
      uses sla:kpi-monitoring-object-grouping;
      description
        "List of dynamic KPI report information for SLA contracts with this
        CC.";
    }
  }

  list cc {
    key "id";
    config false;

    description
      "Current traffic state of all the PCN-2 interfaces of the Colored Clouds
      of the Protected Core. ";

    uses cc-state-grouping;

    container metadata {
      uses nmcd:instance-version-grouping;

      description
        "Metadata information of this dynamic data instance";
    }
  }
}
