module FMN-NMCD-SLA {
	yang-version 1.1;
	namespace "http://FMN/NMCD/SLA";
	prefix nmcdsla;
	
	organization
		"FMN-PCS";
	
	contact 
		"
		editor: Dermul Bart 
				<bart.dermul@mil.be>
		";
	description 
		"
		This module contains the contrat SLA information. 
		Documents describing this model are found in the spiral 4 specifications.
		FMN Tidepedia as source.
		This version of this YANG module is part of FMN-XXX; see the documentation for
		all details.
		Standard: https://tools.ietf.org/html/rfc7950
		";
/* 
 * Revision information
 */
	
	
	revision 2020-03-01 {
		description "Initial draft of the NMCD Yang model.";
		reference "added this as free field when needed Part of the YANG RFC7950 standard";
	}
/* 
 * TypeDefs
 */




}
