module bookshop {
	yang-version 1.1;
	namespace 'http://books.com/bookshop';
	prefix bs;
	
	revision 2020-03-01 {
		description "Initial draft of the NMCD Yang model.";
	}
	
	typedef language-type {
		type enumeration {
			enum Arabic;
			enum Dutch;
			enum Chinese;
			enum Swahili;
		}
		description "Primary Language the book consumer needs to master";
	}
	
	typedef ISBN-10-or-13 {
		type union {
			type string {
				length 10;
				pattern '[0-9]{9}[0-9X]';
			}
			type string {
				length 13;
				pattern '97[89][0-9]{10}';
			}
		}
		description "The international standard book number";
	}
	
	identity format-idty {
		description "Root identy of all book formats";
	}
	identity paper {
		base format-idty;
		description "Physical book print";
	}
	identity audio-cd {
		base format-idty;
		description "digital spoken version";
	}
	identity file-idty {
		base format-idty;
		description "book is delivered as a file";
	}
	identity paperback {
		base paper;
		description " Physical book with soft cover";
	}
	identity hardcover {
		base paper;
		description "Physical book with hardcover";
	}
	identity mp3 {
		base audio-cd;
		description "Audio book delivered as a MP3";
	}
	identity epub {
		base file-idty;
		description "Digital book with epub format";
	}
	identity pdf {
		base file-idty;
		description "Digital book with pdf format";
	}	
	
	
	container books {
		list book {
			key title;
			leaf title {
				type string;
			}
			leaf isbn {
				type ISBN-10-or-13;
			}
			leaf author {
				type leafref {
					path /authors/author/name;
				}
			}
			leaf language {
				type language-type;
			}
			leaf price {
				type decimal64 {
					fraction-digits 2;
				}
				units sim-dollar;
			}
			list format {
				key isbn;
				leaf isbn {
					type ISBN-10-or-13;
				}
				leaf format-id {
					mandatory true;
					type identityref{
						base format-idty;
					}
				}
			}
		}
	}
	
	container users {
		list user {
			key user-id;
			leaf user-id {
				type string;
			}
			leaf name {
				type string;
			}
		}
	}
	
	container authors {
		list author {
			key name;
			leaf name {
				type string;
			}
			leaf account-id {
				type uint32 {
					range 1001..max;
				}
			}
		}
	}
	
	
	
	
	
	
	
	
	
	
	
	
	
	
	
	
	
	
}
