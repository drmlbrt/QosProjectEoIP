module fmn-nmcd-pcore {
	yang-version 1.1;
	namespace "urn:fmn:params:xml:ns:yang:nmcd-pcore";
	prefix nmcdsla;

	import ietf-yang-types {
		prefix yang;
	}
	
	organization
		"FMN-PCS";
	
	contact 
		"
		editor: Dermul Bart 
				<bart.dermul@mil.be>
		";
	description 
		"
		This module contains the contrat SLA information. 
		Documents describing this model are found in the spiral 4 specifications.
		FMN Tidepedia as source.
		This version of this YANG module is part of FMN-XXX; see the documentation for
		all details.
		Standard: https://tools.ietf.org/html/rfc7950
		";
/* 
 * Revision information
 */
	
	
	revision 2019-12-31 {
		description 
		"Initial draft of the NMCD Yang model.";
		reference 
		"added this as free field when needed Part of the YANG RFC7950 standard";
	}
/* 
 * TypeDefs
 */


/*
 *Containers
 */

	container pcore {
		list fmn-nmcd-pcs.pcs{
			key "id";	
			leaf id {
				type uint32 ;
			}
			container metadata {
				leaf version {
					type yang:counter64 ; 
				}
				leaf updated {
					type yang:date-and-time ;
				}
			}
			description "";
		}
		list fmn-nmcd-pcs-state.pcs {
			key "id";	
			leaf id {
				type uint32;
			}
			container metadata {
				leaf version {
					type yang:counter64 ;
				}
				leaf updated {
					type yang:date-and-time ;
				}
			}	
			description "";
		}
		list fmn-nmcd-cc.cc {
			key "id";	
			leaf id {
				type uint32;
			}
			leaf originator-id {
				type uint32 ;
			}
			container metadata {
			
				leaf version {
					type yang:counter64 ;
				}
				leaf updated {
					type yang:date-and-time ;
				}
			}
			description "";		
		}
		list fmn-nmcd-cc-state.cc {
			key "id";	
			leaf id {
				type uint32 ;
			}
			leaf originator-id {
				type uint32 ;
			}
			container metadata {
				leaf version{
					type yang:counter64 ;
				}
				leaf updated {
					type yang:date-and-time ;
				}
			}	
			description "";
		}	
		list fmn-nmcd-sla.sla {
			key "id";	
			leaf id {
				type string ;
			}
			container metadata {
				leaf version {
					type yang:counter64 ;
				}
				leaf updated {
					type yang:date-and-time ;
				}
			}	
			description "";
		}
		list fmn-nmcd-sla-report.sla {
			key "id";	
			leaf id {
				type string ;
			}
			container metadata {
				leaf version {
					type yang:counter64;
				}
				leaf updated {
					type yang:date-and-time;
				}
			}	
			description "";
		}
	}
}
